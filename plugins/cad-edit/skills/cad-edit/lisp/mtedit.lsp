(defun mt-get (h / ed s) (setq ed (entget (handent h)) s "") (foreach x ed (if (= (car x) 3) (setq s (strcat s (cdr x))))) (strcat s (cdr (assoc 1 ed))))
(defun mt-put (h s / ed out chunks i n len)
  (setq ed (entget (handent h)) out nil)
  (foreach x ed (if (not (member (car x) (list 1 3))) (setq out (cons x out))))
  (setq out (reverse out) n (strlen s) i 1 chunks nil)
  (while (> (- n i) 249)
    (setq len 250)
    (while (= (substr s (+ i len -1) 1) (chr 92)) (setq len (1- len)))
    (setq chunks (cons (cons 3 (substr s i len)) chunks)) (setq i (+ i len)))
  (setq out (append out (reverse chunks) (list (cons 1 (substr s i)))))
  (entmod out) (princ (strcat "\nMT-PUT " h " len=" (itoa n) " OK")))
(defun str-rep (s old new / k) (setq k (vl-string-search old s)) (if k (strcat (substr s 1 k) new (substr s (+ k 1 (strlen old)))) s))
(defun BR () (strcat (chr 92) "P"))
